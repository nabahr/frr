// SPDX-License-Identifier: BSD-2-Clause
module frr-pim-rp {
  yang-version "1.1";
  namespace "http://frrouting.org/yang/pim-rp";

  prefix frr-pim-rp;

  import ietf-inet-types {
    prefix "inet";
  }

  import frr-routing {
    prefix "frr-rt";
  }

  import frr-pim {
    prefix "frr-pim";
  }

  import frr-route-types {
    prefix frr-route-types;
  }

  import frr-interface {
    prefix "frr-interface";
  }

  import frr-interface {
    prefix "frr-interface";
  }

  organization
    "FRRouting";

  contact
    "FRR Users List:       <mailto:frog@lists.frrouting.org>
     FRR Development List: <mailto:dev@lists.frrouting.org>";

  description
    "The module defines a collection of YANG definitions common for
     all PIM (Protocol Independent Multicast) RP (Rendezvous Point) model.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2024-09-26 {
    description
      "Add support for embedded RP.";
    reference
      "RFC 3956: Embedding the Rendezvous Point (RP) Address in an IPv6
       Multicast Address";
  }

  revision 2017-03-09 {
    description
      "Initial revision.";
    reference
      "RFC XXXX: A YANG Data Model for PIM RP";
  }

  typedef plist-ref {
    type string;
  }

  /*
   * Groupings
   */
  grouping static-rp-container {
    description
      "Grouping of static RP container.";

    container static-rp {
      description
        "Containing static RP attributes.";

      list rp-list {
        key "rp-address";
        description
          "A list of RP addresses.";

        leaf rp-address {
          type inet:ip-address;
          description
            "Specifies a static RP address.";
        }

        choice group-list-or-prefix-list {
          description "Use group-list or prefix-list";
          case group-list {
            leaf-list group-list{
              type frr-route-types:ip-multicast-group-prefix;
              description
                "List of multicast group address.";
            }
          }
          case prefix-list {
            leaf prefix-list {
              type plist-ref;
              description
                "Group prefix-list filter";
            }
          }
        }
      }
    } // static-rp
  } // static-rp-container

  grouping embedded-rp-group {
    container embedded-rp {
      description "Embedded RP configurations.";

      leaf enable {
        description
          "Toggle embedded RP state:

           When enabled the learned RP from the multicast group address
           will be preferred over any static or dynamic RP configuration.

           When disabled the packet will be processed as usual.";
        type boolean;
        default "false";
      }

      leaf group-list {
        description
          "Restrict embedded RP prefix ranges.

           The default is to treat all multicast groups in FF70::/12
           range as embedded RP. When a group prefix list is configured
           and group does not match one of its permit entries it will
           be treated as regular multicast group.";
        type plist-ref;
      }

      leaf maximum-rps {
        description
          "Maximum allowed number of RPs to learn.";
        type uint32;
        default 25;
      }
    } // embedded-rp container
  } // embedded-rp group

  grouping auto-rp-container {
    description
      "Grouping of AutoRP container.";

    container auto-rp {
      description
        "Containing AutoRP attributes.";

      leaf discovery-enabled {
        type boolean;
        description
          "Flag indicating if Auto RP discovery is enabled.";
      }

      container candidate-rp {
        presence
          "Enable router to be a Candidate RP.";

        description
          "Candidate RP settings";

        leaf scope {
          type uint8;
          description
            "The TTL of the C-RP Announcement packet.";
        }

        leaf interval {
          type uint16;
          description
            "The time between sending C-RP announcement packets (seconds).";
        }

        leaf holdtime {
          type uint16;
          description
            "The hold time in seconds advertised in the announcement packet.";
        }

        choice source-address-or-interface {
          description "IP address to use for RP operation";
          default if-loopback;
          leaf address {
            type inet:ip-address;
          }
          leaf interface {
            type frr-interface:interface-ref;
          }
          leaf if-loopback {
            type empty;
          }
          leaf if-any {
            type empty;
          }
        }

        choice group-or-prefix-list {
          description "Use group or prefix-list";
          case group {
            leaf group {
              type frr-route-types:ip-multicast-group-prefix;
              description
                "Multicast group prefix.";
            }
          }
          case prefix-list {
            leaf prefix-list {
              type plist-ref;
              description
                "Group prefix-list filter";
            }
          }
        }
      } // candidate-rp

      container mapping-agent {
        leaf send-rp-discovery {
          type boolean;
          default false;
          description
            "Make this router an AutoRP mapping agent";
        }

        leaf discovery-scope {
          type uint8;
          default 31;
          description
            "The TTL of the discovery packet";
        }

        leaf discovery-interval {
          type uint16 {
            range "1 .. 65535";
          }
          default 60;
          description
            "The time between sending discovery advertisements (seconds)";
        }

        leaf discovery-holdtime {
          type uint16 {
            range "0 .. 65535";
          }
          default 180;
          description
            "The hold time in seconds advertised in the discovery packet.";
        }

        choice source-address-or-interface {
          description "Source address to use for mapping agent operation";
          default if-loopback;
          leaf address {
            type inet:ip-address;
          }
          leaf interface {
            type frr-interface:interface-ref;
          }
          leaf if-loopback {
            type empty;
          }
          leaf if-any {
            type empty;
          }
        }
      } // mapping-agent
    } // auto-rp
  } // auto-rp-container

  /*
   * Configuration data nodes
   */
  augment "/frr-rt:routing/frr-rt:control-plane-protocols/"
    + "frr-rt:control-plane-protocol/frr-pim:pim/"
    + "frr-pim:address-family" {
    description "PIM RP augmentation.";

    container rp {
      description
        "PIM RP configuration data.";
      uses static-rp-container;

      uses auto-rp-container {
        when "../frr-pim:address-family = 'frr-rt:ipv4'" {
          description
            "Only applicable to IPv4 address family.";
        }
      }

      uses embedded-rp-group {
        when "../frr-pim:address-family = 'frr-rt:ipv6'" {
          description
            "Only available for IPv6 addresses.";
        }
      }
    } // rp
  } // augment
}
